FME workspace FishboneReporting_InternalGeocoding.fmw

Parameters:
- GeocodingGroup =   # Geocoding Options
- MESSAGE_1 =
- FishboneLengthThreshold = 10560   # Fishbone Length Threshold

Note: Note: This tool has been somewhat optimized for performance, but is still slow when dealing with large datasets. Consider this when running it or scheduling it. / For better perfomance, turning off feature caching is also recommended
Note: IMPORTANT!! / This is a placeholder. Replace this with a reader. / Expecting an address point layer. Two fields are required: / 1. Full address field. / 2. A zone field (city specifically, but others may work as well).
Note: Expecting a road centerline layer with the following fields as they are set in the NENA Data Model v3.0: / FromAddr_L / ToAddr_L / FromAddr_R / ToAddr_R / St_PreMod / St_PreDir / St_PreTyp / St_PreSep / St_Name / St_PosTyp / St_PosDir / St_PosMod / A1_L / A1_R / A2_L / A2_R / A3_L / A3_R / A4_L / A4_R
Note: Exclude exceptions early for performance reasons
Junction_4
    -> early_exclusions
Note: Note: Consider setting the resampling method to bilinear or higher if spatial accuracy is a concer. This will incur a significant performance penalty, though
Note: Reproject to desired coordinate system. Pay attention to the units used
Reprojector
    DEST = EPSG:2274
    INTERPOLATION_TYPE = NearestNeighbor
    RASTER_CELL_SIZE = PreserveCells
    RASTER_TOLERANCE = 0.0
    SOURCE = EPSG:4326
    REPROJECTED -> create_fields
Note: Create and calculate all fields necessary to split original segments into smaller segments for 1-to-1 matching with address points. The general logic for these fields goes: (the same applies to the each side) / 1. Get the segment length / 2. Get the range covered by each side (Example: if left from is 12 and left to is 18, this number is 6 / 3. Divide this number by half to know how many times the first indexed range (FromTo) will need to be incremented. Add 1 to make this number even (to avoid the ranges of 13, 15, and 17 in the previous example - as this is the even side of the road) / 4. We want to split the original sement into many smaller ones based on the numeric ranges covered on that side. Divide the total length by the increment we just calculated to determine the length of these new small segments. Example below. / Variables: / - Total length of original segment: 20m / - FromAddr value: 12 / - ToAddr value: 18 / ...from this, we can calculate this: / _range: 6 / _increment: 4 / _intervallength: 5 / ...and graphically, we get these results: / |------------------| (original segment, each "-"and "|" == 1m) / 12-18 / |---||---||---||---| (total/_intervallength == 4 segments of 5m each) / 12 14 16 18
Note: Create critial fields
create_fields: AttributeCreator
    ATTR_TABLE:
      SET_TO _seglength (varchar(200)) = @Length()
      SET_TO _leftrange (real64) = @Evaluate(@Evaluate(@Value(ToAddr_L)-@Value(FromAddr_L)))
      SET_TO _rightrange (real64) = @Evaluate(@Evaluate(@Value(ToAddr_R)-@Value(FromAddr_R)))
      SET_TO _leftincrement (varchar(200)) = FME_CONDITIONAL:DEFAULT_VALUE'ERROR'BOOL_OP;OR;COMPOSITE_TEST;1 OR 2 OR 3 OR 4 OR 5;CASE_INSENSITIVE_TEST @Evaluate(@Evaluate((@Value(_leftrange)/2))) ENDS_WITH 1;CASE_INSENSITIVE_TEST @Evaluate(@Evaluate((@Value(_leftrange)/2))) ENDS_WITH 3;CASE_INSENSITIVE_TEST @Evaluate(@Evaluate((@Value(_leftrange)/2))) ENDS_WITH 5;CASE_INSENSITIVE_TEST @Evaluate(@Evaluate((@Value(_leftrange)/2))) ENDS_WITH 7;CASE_INSENSITIVE_TEST @Evaluate(@Evaluate((@Value(_leftrange)/2))) ENDS_WITH 9'@Evaluate(@Evaluate((@Value(_leftrange)/2)+1))'BOOL_OP;OR;COMPOSITE_TEST;1 OR 2 OR 3 OR 4 OR 5;CASE_INSENSITIVE_TEST @Evaluate(@Evaluate((@Value(_leftrange)/2))) ENDS_WITH 0;CASE_INSENSITIVE_TEST @Evaluate(@Evaluate((@Value(_leftrange)/2))) ENDS_WITH 2;CASE_INSENSITIVE_TEST @Evaluate(@Evaluate((@Value(_leftrange)/2))) ENDS_WITH 4;CASE_INSENSITIVE_TEST @Evaluate(@Evaluate((@Value(_leftrange)/2))) ENDS_WITH 6;CASE_INSENSITIVE_TEST @Evaluate(@Evaluate((@Value(_leftrange)/2))) ENDS_WITH 8'@Evaluate(@Evaluate((@Value(_leftrange)/2)))'FME_NUM_CONDITIONS3___
      SET_TO _rightincrement (varchar(200)) = FME_CONDITIONAL:DEFAULT_VALUE'ERROR'BOOL_OP;OR;COMPOSITE_TEST;1 OR 2 OR 3 OR 4 OR 5;CASE_INSENSITIVE_TEST @Evaluate(@Evaluate((@Value(_rightrange)/2))) ENDS_WITH 1;CASE_INSENSITIVE_TEST @Evaluate(@Evaluate((@Value(_rightrange)/2))) ENDS_WITH 3;CASE_INSENSITIVE_TEST @Evaluate(@Evaluate((@Value(_rightrange)/2))) ENDS_WITH 5;CASE_INSENSITIVE_TEST @Evaluate(@Evaluate((@Value(_rightrange)/2))) ENDS_WITH 7;CASE_INSENSITIVE_TEST @Evaluate(@Evaluate((@Value(_rightrange)/2))) ENDS_WITH 9'@Evaluate(@Evaluate((@Value(_rightrange)/2)+1))'BOOL_OP;OR;COMPOSITE_TEST;1 OR 2 OR 3 OR 4 OR 5;CASE_INSENSITIVE_TEST @Evaluate(@Evaluate((@Value(_rightrange)/2))) ENDS_WITH 0;CASE_INSENSITIVE_TEST @Evaluate(@Evaluate((@Value(_rightrange)/2))) ENDS_WITH 2;CASE_INSENSITIVE_TEST @Evaluate(@Evaluate((@Value(_rightrange)/2))) ENDS_WITH 4;CASE_INSENSITIVE_TEST @Evaluate(@Evaluate((@Value(_rightrange)/2))) ENDS_WITH 6;CASE_INSENSITIVE_TEST @Evaluate(@Evaluate((@Value(_rightrange)/2))) ENDS_WITH 8'@Evaluate(@Evaluate((@Value(_rightrange)/2)))'FME_NUM_CONDITIONS3___
      SET_TO _intervallength_l (real64) = @Evaluate(@Evaluate(@Value(_seglength)/(@Value(_leftincrement))))
      SET_TO _intervallength_r (real64) = @Evaluate(@Evaluate(@Value(_seglength)/(@Value(_rightincrement))))
      SET_TO _countinglabel_l (varchar(200)) = @FullTitleCase(@Value(FromAddr_L)-@Value(ToAddr_L)-@Value(St_PreMod)-@Value(St_PreDir)-@Value(St_PreTyp)-@Value(St_PreSep)-@Value(St_Name)-@Value(St_PosTyp)-@Value(St_PosDir)-@Value(St_PosMod)-@Value(A1_L)-@Value(A2_L)-@Value(A3_L)-@Value(A4_L))
      SET_TO _countinglabel_r (varchar(200)) = @FullTitleCase(@Value(FromAddr_R)-@Value(ToAddr_R)-@Value(St_PreMod)-@Value(St_PreDir)-@Value(St_PreTyp)-@Value(St_PreSep)-@Value(St_Name)-@Value(St_PosTyp)-@Value(St_PosDir)-@Value(St_PosMod)-@Value(A1_L)-@Value(A2_R)-@Value(A3_R)-@Value(A4_R))
    INPUT_PORT_CONNECTED = CONNECTED
    -> FullName_RCL
Note: Concatenate full name field (used for reporting)
FullName_RCL: Full Name
    ST_NAME = @Value(St_Name)
    ST_POSDIR = @Value(St_PosDir)
    ST_POSMOD = @Value(St_PosMod)
    ST_POSTYP = @Value(St_PosTyp)
    ST_PREDIR = @Value(St_PreDir)
    ST_PREMOD = @Value(St_PreMod)
    ST_PRESEP = @Value(St_PreSep)
    ST_PRETYP = @Value(St_PreTyp)
    -> Densifier_l
    -> Densifier_r
Note: Create vertices along side the original segment in intervals using the _intervallength attribute that we calculated previously. / Then split the original segment at those vertices
Densifier_l
    INTERVAL = @Value(_intervallength_l)
    MODE_LOOKUP = xy
    MODE = Exact Interval
    DENSIFIED -> Chopper_l
Chopper_l
    APPROX_LENGTH = @Value(_intervallength_l)
    DEAGGREGATE_INPUT = Deaggregate
    GRID_AREAS = Yes
    MODE_LOOKUP = LENGTH
    MODE = By Length
    CHOPPED -> _count_l
Note: Count the number of new segments based on groups (what _matchlabel is needed for). This way we know how many new segments exist for each original segment (the group)
_count_l: Counter
    CNT_ATTR = _count
    GROUP_BY = _countinglabel_l
    SCOPE = Local
    START = 1
    -> calculate_new_range_l
Note: And calculate the range that each point represents (formerly the new segments). Create new matchlabel that includes this number. This will be a 1-to-1 match with incoming points
calculate_new_range_l: AttributeCreator
    ATTR_TABLE:
      SET_TO _leftrangenumber (real64) = @Evaluate(@Value(FromAddr_L)+((@Value(_count)-1)*2))
      SET_TO _matchlabel_withzone (varchar(200)) = @Value(_leftrangenumber)-@FullTitleCase(@Value(St_PreMod)-@Value(St_PreDir)-@Value(St_PreTyp)-@Value(St_PreSep)-@Value(St_Name)-@Value(St_PosTyp)-@Value(St_PosDir)-@Value(St_PosMod)-@Value(A1_L)-@Value(A2_L)-@Value(A3_L)-@Value(A4_L))
    INPUT_PORT_CONNECTED = CONNECTED
    -> CoordinateExtractor_l
Note: Extract the coordinates of the first index value for each of these segments
CoordinateExtractor_l
    IND = 0
    RECURSIVE = No
    X_ATTR = _x
    Y_ATTR = _y
    MODE = Specify Coordinate
    -> VertexCreator_l
Note: Then replace the line geometry of each segment with the coordinates of that first index
VertexCreator_l
    MEASURE_TYPE_LOOKUP = CONTINUOUS
    MODE = REPLACE
    REMOVE_ATTRIBUTES = No
    XVAL = @Value(_x)
    YVAL = @Value(_y)
    MEASURE_TYPE = Continuous
    MODE_NAME = Replace with Point
    -> remove_duplicates
Densifier_r
    INTERVAL = @Value(_intervallength_r)
    MODE_LOOKUP = xy
    MODE = Exact Interval
    DENSIFIED -> Chopper_r
Chopper_r
    APPROX_LENGTH = @Value(_intervallength_r)
    DEAGGREGATE_INPUT = Deaggregate
    GRID_AREAS = Yes
    MODE_LOOKUP = LENGTH
    MODE = By Length
    CHOPPED -> _count_r
_count_r: Counter
    CNT_ATTR = _count
    GROUP_BY = _countinglabel_r
    SCOPE = Local
    START = 1
    -> calculate_new_range_r
calculate_new_range_r: AttributeCreator
    ATTR_TABLE:
      SET_TO _rightrangenumber (real64) = @Evaluate(@Evaluate(@Value(FromAddr_R)+((@Value(_count)-1)*2)))
      SET_TO _matchlabel_withzone (varchar(200)) = @Value(_rightrangenumber)-@FullTitleCase(@Value(St_PreMod)-@Value(St_PreDir)-@Value(St_PreTyp)-@Value(St_PreSep)-@Value(St_Name)-@Value(St_PosTyp)-@Value(St_PosDir)-@Value(St_PosMod)-@Value(A1_L)-@Value(A2_R)-@Value(A3_R)-@Value(A4_R))
    INPUT_PORT_CONNECTED = CONNECTED
    -> CoordinateExtractor_r
CoordinateExtractor_r
    IND = 0
    RECURSIVE = No
    X_ATTR = _x
    Y_ATTR = _y
    MODE = Specify Coordinate
    -> VertexCreator_r
VertexCreator_r
    MEASURE_TYPE_LOOKUP = CONTINUOUS
    MODE = REPLACE
    REMOVE_ATTRIBUTES = No
    XVAL = @Value(_x)
    YVAL = @Value(_y)
    MEASURE_TYPE = Continuous
    MODE_NAME = Replace with Point
    -> remove_duplicates
remove_duplicates: DuplicateFilter
    INPUT_ORDERED_CHOICE_LOOKUP = YES
    KEYATTR = _matchlabel_withzone
    INPUT_ORDERED_CHOICE = Yes
    UNIQUE -> matcher
Note: IMPORTANT!! / This is a placeholder. Replace this with a reader. / Expecting an address point layer. Two fields are required: / 1. Full address field. / 2. A zone field (city specifically, but others may work as well).
Note: Expecting a road centerline layer with the following fields as they are set in the NENA Data Model v3.0: / Add_Number / St_PreMod / St_PreDir / St_PreTyp / St_PreSep / St_Name / St_PosTyp / St_PosDir / St_PosMod / A1 / A2 / A3 / A4
Junction_5
    -> reproject_points
Note: Set projection to the same one that the streets are using
reproject_points: Reprojector
    DEST = EPSG:2274
    INTERPOLATION_TYPE = Bilinear
    RASTER_CELL_SIZE = PreserveCells
    RASTER_TOLERANCE = 0.0
    SOURCE = EPSG:4326
    REPROJECTED -> match_label_ap
Note: Create matching label
match_label_ap: AttributeCreator
    ATTR_TABLE = SET_TO _matchlabel_withzone (varchar(200)) = @FullTitleCase(@Value(Add_Number)-@Value(St_PreMod)-@Value(St_PreDir)-@Value(St_PreTyp)-@Value(St_PreSep)-@Value(St_Name)-@Value(St_PosTyp)-@Value(St_PosDir)-@Value(St_PosMod)-@Value(A1)-@Value(A2)-@Value(A3)-@Value(A4))
    INPUT_PORT_CONNECTED = CONNECTED
    -> matcher
Note: Match address points with their corresponding part of the segment that was calculated in the range splitting transformer
matcher: Matcher
    BLANK_AND_MISSING_DIFFER = No
    CHECK_TYPES_AND_ENCODINGS = No
    CNT_ATTR = _match_id
    MATCHATTRS = _matchlabel_withzone
    MATCH_STRATEGY_LOOKUP = MATCH
    MATCH_STRATEGY = Match Selected Attributes
    MATCHED -> create_full_address
    NOT_MATCHED -> create_full_address_3
Note: Then concatenate with address number to create a "full address" field
create_full_address: StringConcatenator
    ACTION = Create New Attribute
    PARM_LINE = fme_basicstring:18%1%17:@Value(Add_Number) @Value(_FullName)
    VAL_ATTR = Address
    -> build_fishbones
Note: Connect the interpolated position along a centerline with the actual location of the address point. This constitutes a fishbone
build_fishbones: LineBuilder
    ACCUM_INPUT_ATTRS_LOOKUP = All
    GROUP_BY = _match_id
    REMOVE_DUPLICATES_LOOKUP = NO
    ACCUM_INPUT_ATTRS = Merge Incoming Attributes
    REMOVE_DUPLICATES = No
    LINE -> attr_mngr_fishbones
Note: Manage attributes and set up reporting fields
attr_mngr_fishbones: AttributeManager
    ATTR_TABLE:
      REMOVE _matchlabel_withzone (varchar(200))
      REMOVE A1_L (varchar(200))
      REMOVE A1_R (varchar(200))
      REMOVE A2_L (varchar(200))
      REMOVE A2_R (varchar(200))
      REMOVE A3_L (varchar(200))
      REMOVE A3_R (varchar(200))
      REMOVE A4_L (varchar(200))
      REMOVE A4_R (varchar(200))
      REMOVE _match_id (uint32)
      REMOVE _leftrangenumber (real64)
      REMOVE _seglength (varchar(200))
      REMOVE _leftrange (real64)
      REMOVE _rightrange (real64)
      REMOVE _leftincrement (varchar(200))
      REMOVE _rightincrement (varchar(200))
      REMOVE _intervallength_l (real64)
      REMOVE _intervallength_r (real64)
      REMOVE _countinglabel_l (varchar(200))
      REMOVE _countinglabel_r (varchar(200))
      REMOVE _count (int64)
      REMOVE _x (real64)
      REMOVE _y (real64)
      REMOVE _rightrangenumber (real64)
      REMOVE _FullName (varchar(200))
    USER_EXPOSED_ATTRIBUTES = _matchlabel_r,_matchlabel_l,_Address,_increment
    -> Junction
Note: Write fishbones
Junction
create_full_address_3: StringConcatenator
    ACTION = Create New Attribute
    PARM_LINE = fme_basicstring:18%1%17:@Value(Add_Number) @Value(_FullName)
    VAL_ATTR = address
    -> exclude_non-points
Note: Exclude all "not matched" results that are coming from the segments themselves. We only care about the points themselves here
exclude_non-points: Tester
    BOOL_OP = OR
    TEST_CLAUSE = TEST Add_Number ATTRIBUTE_HAS_A_VALUE ""
    TEST_MODE = TEST
    PASSED -> Junction_2
Note: Write "failed to geocode" errors
Junction_2

Bookmark: Replace with reader
Creator
    GEOMTYPE = Geometry Object
    NUM = 1
    CREATED -> AttributeCreator
AttributeCreator
    ATTR_TABLE:
      SET_TO FromAddr_L (varchar(200))
      SET_TO ToAddr_L (varchar(200))
      SET_TO FromAddr_R (varchar(200))
      SET_TO ToAddr_R (varchar(200))
      SET_TO St_PreMod (varchar(200))
      SET_TO St_PreDir (varchar(200))
      SET_TO St_PreTyp (varchar(200))
      SET_TO St_PreSep (varchar(200))
      SET_TO St_Name (varchar(200))
      SET_TO St_PosTyp (varchar(200))
      SET_TO St_PosDir (varchar(200))
      SET_TO St_PosMod (varchar(200))
      SET_TO A1_L (varchar(200))
      SET_TO A1_R (varchar(200))
      SET_TO A2_L (varchar(200))
      SET_TO A2_R (varchar(200))
      SET_TO A3_L (varchar(200))
      SET_TO A3_R (varchar(200))
      SET_TO A4_L (varchar(200))
      SET_TO A4_R (varchar(200))
    -> Junction_4

Bookmark: Early exclusions
early_exclusions: TestFilter
    DEFAULT_VALUE = <UNFILTERED>
    PASSED_TEST_GROUP_OUTPUT = FIRST
    TEST_LIST:
      "BOOL_OP,COMPOSITE,COMPOSITE_TEST,""""""NOT ( 1 OR 2 )"""""",TEST_CLAUSE,TEST @Value(FromAddr_L) > @Value(ToAddr_L)
      TEST @Value(FromAddr_R) > @Value(ToAddr_R)",From Higher Than To,"BOOL_OP,AND,COMPOSITE_TEST,""""""1 AND 2"""""",TEST_CLAUSE,TEST @Evaluate(@Value(ToAddr_L)-@Value(FromAddr_L)) = 0
      TEST @Evaluate(@Value(ToAddr_R)-@Value(FromAddr_R)) = 0",Both 1-1,"BOOL_OP,COMPOSITE,COMPOSITE_TEST,""""""( NOT 1 AND 2 ) OR ( NOT 3 AND 4 ) OR ( 5 AND 6 ) OR ( 7 AND 8 )"""""",TEST_CLAUSE,TEST @Value(FromAddr_L) = 0
      TEST @Value(ToAddr_L) = 0
      TEST @Value(FromAddr_R) = 0
      TEST @Value(ToAddr_R) = 0
      TEST @Value(FromAddr_L) = 0
      TEST @Value(ToAddr_L) NOT_= 0
      TEST @Value(FromAddr_R) = 0
      TEST @Value(ToAddr_R) NOT_= 0",Mixed with zero
    <UNFILTERED> -> Reprojector

Bookmark: Replace with reader
Creator_2
    GEOMTYPE = Geometry Object
    NUM = 1
    CREATED -> AttributeCreator_2
AttributeCreator_2
    ATTR_TABLE:
      SET_TO Add_Number (varchar(200))
      SET_TO St_PreMod (varchar(200))
      SET_TO St_PreDir (varchar(200))
      SET_TO St_PreTyp (varchar(200))
      SET_TO St_PreSep (varchar(200))
      SET_TO St_Name (varchar(200))
      SET_TO St_PosTyp (varchar(200))
      SET_TO St_PosDir (varchar(200))
      SET_TO St_PosMod (varchar(200))
      SET_TO A1 (varchar(200))
      SET_TO A2 (varchar(200))
      SET_TO A3 (varchar(200))
      SET_TO A4 (varchar(200))
    -> Junction_5

FME custom transformer Full Name

Parameters:
- ST_NAME = @Value(St_Name)   # St Name
- ST_POSDIR = @Value(St_PosDir)   # St Posdir
- ST_POSMOD = @Value(St_PosMod)   # St Posmod
- ST_POSTYP = @Value(St_PosTyp)   # St Postyp
- ST_PREDIR = @Value(St_PreDir)   # St Predir
- ST_PREMOD = @Value(St_PreMod)   # St Premod
- ST_PRESEP = @Value(St_PreSep)   # St Presep
- ST_PRETYP = @Value(St_PreTyp)   # St Pretyp
- FME_PROCESS_GROUP_BY =   # "" Group By
- FME_PROCESS_GROUPS_ORDERED = No   # When All Features Received,No%When Group Changes (Advanced),Yes Complete Groups

Input (input)
    -> Create_Full_Name
Create_Full_Name: AttributeCreator
    ATTR_TABLE = SET_TO _FullName (varchar(200)) = @Value(St_PreMod)-@Value(St_PreDir)-@Value(St_PreTyp)-@Value(St_PreSep)-@Value(St_Name)-@Value(St_PosTyp)-@Value(St_PosDir)-@Value(St_PosMod)
    -> replace_spec_chrtrs
loop_start (input)
    -> replace_spec_chrtrs
replace_spec_chrtrs: StringReplacer
    CASE = NO
    FIND_TEXT = -
    NO_MATCH = _FME_NO_OP_
    REGEXP = YES
    REPLACE_TEXT = " "
    SRC_ATTRS = _FullName
    -> clean_up_blanks
clean_up_blanks: StringReplacer
    CASE = NO
    FIND_TEXT = "  "
    NO_MATCH = _FME_NO_OP_
    REGEXP = YES
    REPLACE_TEXT = " "
    SRC_ATTRS = _FullName
    -> trim_ends
trim_ends: AttributeTrimmer
    SRC_ATTRS = _FullName
    TRIM_CHARS = " "
    TRIM_TO_NONE = Yes
    TRIM_TYPE = BOTH
    -> if_spaces_found
if_spaces_found: Tester
    BOOL_OP = OR
    TEST_CLAUSE:
      CASE_INSENSITIVE_TEST @Value(_FullName) CONTAINS_REGEX
      CASE_INSENSITIVE_TEST @Value(_FullName) BEGINS_WITH
      CASE_INSENSITIVE_TEST @Value(_FullName) ENDS_WITH
    TEST_MODE = CASE_INSENSITIVE_TEST
    PASSED -> loop_start (output)
    FAILED -> Output (output)
loop_start (output)
Output (output)
